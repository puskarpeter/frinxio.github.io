module netconf-node-topology {
    namespace "urn:opendaylight:netconf-node-topology";
    prefix "nettop";

    import network-topology { prefix nt; revision-date 2013-10-21; }
    import yang-ext { prefix ext; revision-date "2013-07-09";}
    import ietf-inet-types { prefix inet; revision-date "2013-07-15"; }
    import connection-manager { prefix cm; revision-date "2021-04-09"; }

    revision "2015-01-14" {
        description "Initial revision of Topology model";
    }

    augment "/nt:network-topology/nt:topology/nt:topology-types" {
        container topology-netconf {
        }
    }

    grouping username-password {
        leaf username {
            type string;
        }

        leaf password {
            type string;
        }
    }

    grouping netconf-node-credentials {
        choice credentials {
            config true;
            case login-password {
                description "Deprecated way of storing credentials, unencrypted.";

                status deprecated;
                uses username-password;
            }
            case login-pw {
                description "login-password credentials, encrypted.";

                container login-password {
                    uses username-password;
                }
            }
            case login-pw-unencrypted {
                description "login-password credentials, not encrypted.";

                container login-password-unencrypted {
                    uses username-password;
                }
            }
            case key-auth {
                description "key-based authentication, use the id for the pair thats stored in the keystore.";

                container key-based {
                    leaf key-id {
                        type string;
                    }

                    leaf username {
                        type string;
                    }
                }
            }
        }
    }

    grouping common-session-timers {
        leaf max-connection-attempts {
            description "Maximum number of connection retries. Non positive value or null is interpreted as infinity.";
            config true;
            type uint32;
            default 1;
        }

        leaf max-reconnection-attempts {
            description "Maximum number of reconnect retries. Non positive value or null is interpreted as infinity.
                         This is an optional parameter. If set, max-connection-attempts will be used only once, for the first connection attempts
                         and for any subsequent disconnect-connect cycles, max-reconnect-attempts will be used.
                         This enables users using different amount of reconnects for initial attempts vs subsequent reconnects.";
            config true;
            type uint32;
            default 0;
        }

        leaf keepalive-delay {
            config true;
            type uint32;
            default 120;
            description "Netconf connector sends keepalive RPCs while the session is idle, this delay specifies the delay between keepalive RPC in seconds
                         If a value <1 is provided, no keepalives will be sent";
        }
    }

    grouping common-flags {
        leaf enabled-notifications {
            config true;
            type boolean;
            default true;
            description "If it is set to 'true' and NETCONF device supports notifications, NETCONF mountpoint will
                         expose NETCONF notification and subscription services.";
        }

        leaf reconnect-on-changed-schema {
            config true;
            type boolean;
            default false;
            description "If it is set to 'true', NETCONF notifications are supported by device, and NETCONF
                         notifications are enabled ('enabled-notifications' flag), the connector would auto
                         disconnect/reconnect when schemas are changed in the remote device. The connector subscribes
                         (right after connect) to base netconf notifications and listens
                         for netconf-capability-change notification";
        }

        leaf streaming-session {
            description "NETCONF session is created and optimized for receiving of NETCONF notifications
                         from remote server.";
            config true;
            default false;
            type boolean;
        }
    }

    grouping common-other-parameters {
        leaf concurrent-rpc-limit {
            config true;
            type uint16;
            default 0;
            description "Limit of concurrent messages that can be send before reply messages are received.
                         If value <1 is provided, no limit will be enforced";
        }

        leaf edit-config-test-option {
            description "Specification of the test-option parameter in the netconf edit-config message.
                         Possible values are 'set', 'test-then-set' or 'test-only'. If the edit-config-test-option is not
                         explicitly specified in the mount request, then the default value will be used ('test-then-set').";
            config true;
            default test-then-set;
            type enumeration {
                enum set;
                enum test-only;
                enum test-then-set;
            }
        }

        leaf dry-run-journal-size {
            type uint16;
            default 0;
            description "Size of the DRY RUN netconf mountpoint journal. DRY RUN journal captures netconf RPCs that
                         would be executed when reading/writing some configuration. However the RPCs are not actually
                         sent to the device";
        }
    }

    grouping common-netconf-parameters {

        uses common-session-timers;

        uses common-flags;

        uses common-other-parameters;
    }

    grouping netconf-node-connection-parameters {

        leaf host {
            type inet:host;
        }

        leaf port {
            type inet:port-number;
        }

        leaf tcp-only {
            config true;
            type boolean;
        }

        leaf schemaless {
            type boolean;
            default false;
        }

        container yang-module-capabilities {
            config true;
            leaf override {
                type boolean;
                default false;
                description "Whether to override or merge this list of capabilities with capabilities from device";
            }

            leaf-list capability {
                type string;
                description "Set a list of capabilities to override capabilities provided in device's hello message.
                             Can be used for devices that do not report any yang modules in their hello message";
            }
        }

        container non-module-capabilities {
            config true;
            leaf override {
                type boolean;
                default false;
                description "Whether to override or merge this list of non-module based capabilities with non-module
                             based capabilities from device";
            }

            leaf-list capability {
                type string;
                description "Set a list of non-module based capabilities to override or merge non-module capabilities
                             provided in device's hello message. Can be used for devices that do not report or
                             incorrectly report non-module based capabilities in their hello message";
            }
        }

        container odl-hello-message-capabilities {
            config true;
            leaf-list capability {
                type inet:uri;
                description "Certain devices are non-accepting of ODL's hello message.  This allows specification of
                             a custom ODL hello message based on a list of supported capabilities.";
            }
        }

        leaf parent-node-id {
            type string;
            config true;
            description "Identifier of the parent node with which the current node shares the lifecycle.";
        }
    }

    grouping netconf-node-connection-status {

        leaf connection-status {
            config false;
            type enumeration {
                enum connecting;
                enum connected;
                enum unable-to-connect;
            }
        }

        container clustered-connection-status {
            config false;
            list node-status {
                leaf node {
                    type string;
                }
                leaf status {
                    type enumeration {
                        enum connected;
                        enum unavailable;
                        enum failed;
                    }
                }
            }
            leaf netconf-master-node {
                config false;
                type string;
            }
        }

        leaf connected-message {
            config false;
            type string;
        }

        container available-capabilities {
            config false;
            list available-capability {
                leaf capability {
                    type string;
                }
                leaf capability-origin {
                    type enumeration {
                        enum user-defined;
                        enum device-advertised;
                    }
                }
            }
        }

        container unavailable-capabilities {
            config false;
            list unavailable-capability {
                leaf capability {
                    type string;
                }

                leaf failure-reason {
                    type enumeration {
                        enum missing-source;
                        enum unable-to-resolve;
                    }
                }
            }
        }

        container pass-through {
            when "../connection-status = connected";
            description
                "When the underlying node is connected, its NETCONF context
                is available verbatim under this container through the
                mount extension.";
        }

    }

    grouping netconf-schema-storage {
        leaf schema-cache-directory {
            config true;
            type string;
            description "The destination schema repository for yang files relative to the cache directory.  This may be specified per netconf mount
                         so that the loaded yang files are stored to a distinct directory to avoid potential conflict.";
        }

        container yang-library {
            leaf yang-library-url {
                config true;
                type inet:uri;
                description "Yang library to be plugged as additional source provider into the shared schema repository";
            }

            // credentials for basic http authentication
            leaf username {
                config true;
                type string;
            }

            leaf password {
                config true;
                type string;
            }
        }
    }

    grouping old-format-of-netconf-parameters {
        leaf connection-timeout-millis {
            description "Specifies timeout in milliseconds after which connection must be established.";
            config true;
            type uint32;
            default 20000;
        }

        leaf default-request-timeout-millis {
            description "Timeout in milliseconds for blocking operations within transactions.";
            config true;
            type uint32;
            default 60000;
        }

        leaf between-attempts-timeout-millis {
            description "Initial timeout in milliseconds to wait between connection attempts. Will be multiplied by sleep-factor with every additional attempt";
            config true;
            type uint16;
            default 2000;
        }

        leaf sleep-factor {
            description "After each reconnection attempt, the delay between reconnection attempts is
                         multiplied by this factor. By default, it is set to 1.5. This means that the next
                         delay between attempts will be 3000 ms, then it will be 4500 ms, etc.";
            config true;
            type decimal64 {
                fraction-digits 1;
            }
            default 1.5;
        }

        leaf confirm-timeout {
            description "Timeout period in seconds to issued commit after confirmed-commit";
            config true;
            type uint32;
            default 600;
        }

        leaf strict-parsing {
            config true;
            type boolean;
            default true;
            description "If this parameter is set to 'false', then parser should ignore unknown elements and not throw
                         exception during parsing.";
        }

        leaf customization-factory {
            description "Specification of the custom NETCONF connector factory. For example,
                        if device doesn't support candidate data-store, this parameter
                        should be set to 'netconf-customization-alu-ignore-candidate' string.";
            config true;
            type string;
            default "default";
        }

        uses common-netconf-parameters;
    }

    grouping session-timers-group {
        leaf initial-connection-timeout {
            description "Specifies timeout in seconds after which connection must be established.";
            config true;
            type uint32;
            default 20;
        }

        leaf request-transaction-timeout {
            description "Timeout in seconds for blocking operations within transactions.";
            config true;
            type uint32;
            default 60;
        }

        leaf between-attempts-timeout {
            description "Initial timeout in seconds to wait between connection attempts.
                         Will be multiplied by reconenction-attempts-multiplier with every additional attempt";
            config true;
            type uint16;
            default 2;
        }

        leaf confirm-commit-timeout {
            description "Timeout period in seconds to issued commit after confirmed-commit";
            config true;
            type uint32;
            default 600;
        }

        leaf reconnenction-attempts-multiplier {
            description "After each reconnection attempt, the delay between reconnection attempts is
                        multiplied by this factor. By default, it is set to 1.5. This means that the next
                        delay between attempts will be 3000 ms, then it will be 4500 ms, etc.";
            config true;
            type decimal64 {
                fraction-digits 1;
            }
            default 1.5;
        }

        uses common-session-timers;
    }

    grouping flags-group {
        leaf enabled-strict-parsing {
            config true;
            type boolean;
            default true;
            description "If this parameter is set to 'false', then parser should ignore unknown elements and not throw
                         exception during parsing.";
        }

        uses common-flags;
    }

    grouping other-parameters-group {
        leaf custom-connector-factory {
            description "Specification of the custom NETCONF connector factory. For example,
                                    if device doesn't support candidate data-store, this parameter
                                    should be set to 'netconf-customization-alu-ignore-candidate' string.";
            config true;
            type string;
            default "default";
        }

        uses common-other-parameters;
    }

    grouping netconf-parameters-groups {

        container session-timers {
            uses session-timers-group;
        }

        container flags {
            uses flags-group;
        }

        container other-parameters {
            uses other-parameters-group;
        }
    }

    grouping both-formats-of-netconf-default-parameters {
        choice netconf-parameters {
            default netconf-parameters-new-format;

            case netconf-parameters-new-format {
                uses netconf-parameters-groups;
            }
            case netconf-parameters-old-format {
                uses old-format-of-netconf-parameters;
            }
        }
    }

    grouping netconf-node-fields {
        uses netconf-node-credentials;

        uses netconf-node-connection-parameters;

        uses netconf-node-connection-status;

        uses netconf-schema-storage;

        uses both-formats-of-netconf-default-parameters;
    }

    container netconf-default-parameters {
        uses netconf-parameters-groups;
    }

    rpc create-device {
        input {
            uses netconf-node-fields;
            leaf node-id {
                type string;
            }
        }
    }

    rpc delete-device {
        input {
            leaf node-id {
                type string;
            }
        }
    }

    augment "/nt:network-topology/nt:topology/nt:node" {
        when "../../nt:topology-types/topology-netconf";
        ext:augment-identifier "netconf-node";

        uses netconf-node-fields;
    }

    augment "/cm:install-node/cm:input/cm:netconf" {
        uses netconf-node-fields;
    }

    augment "/cm:install-multiple-nodes/cm:input/cm:nodes/cm:netconf" {
        uses netconf-node-fields;
    }
}
